# local_sequencer_req
The local sequencer shall provide control and coordination between task function blocks and task memories in order to execute function blocks sequentially while providing inputs to the function blocks from task memories and to store outputs from the function blocks to the task memories.

## #1: Trigger Service Received (Functional)
Shall receive a level sensitive trigger from the global sequencer that initiates task execution.

## #2: Instruction Service Received (Functional)
The local sequencer shall receive a list of instructions in a sequential fashion that includes each function block to be exeucted, the function block input and output task memory addresses.

### #7: End of File Determination (Functional)
The local sequencer shall compare each instruction to see if the end of file flag has been reached.

## #3: Function Block Status Service Received (Functional)
The local sequence shall receive a status signal from the task function blocks that includes a boolean status and error code word.

### #4: Super State Iteration Detection (Functional)
Bits 22 through 27 of the error code shall be extracted, incremented, and compared to the same bits on subsequent execution cycles to see if the function blocks iterated in the same same super state.

### #5: Super State Change Detection (Functional)
The upper four bits of the error code in the status signal shall be extrated and compared to pervious bits to see if a super state change has occured.

### #6: Error Recovery Determination (Functional)
The lower 22 bits of the error code in the status signal shall be extracted and compared to a list of recoverable functions to see if the architecture supports resiliency from the error code experienced.

## #8: Function Number Register (Functional)
At the begining of an instruction sequence (variable length) the first instruction (the function number) shall be latched in an isolated register from the instruction service.

## #9: Start Instruction Pointer Register (Functional)
The begining position of a sequence of instructions shall be latched into an isolated register.
- Rationale: Latching of the first instruction in a sequence of instrucitons is necessary so that the instruction pointer counter can be loaded with this value if a fault is experienced and the instruction sequence must be restarted.

## #10: Instruction Counter (Functional)
A counter will serve as the pointer for the instruction pointer. The counter will be capable of loading a stored begining instruction position so that a sequence can be restarted at the begining of the sequence when a fault is detected.

## #11: Current Address Register (Functional)
The current address in task memory of an input or output to a function block shall have a dedicated register. Addresses shall be latched from an instruction sequence.

## #12: Controller Super States (Functional)

### #13: INIT (Functional)
All controller outputs shall be initialized to false except reset, which is initialized to true.

#### #21: Transistions (Functional)
1) When trigger is true, the controller shall transition to the FB_SELECT super state.

### #14: FB_SELECT (Functional)
If the recoverable input to the controller is true the instruction counter will be loaded with the value stored in the Start Instruction register. Otherwise, the function number register and start instruction pointer register will be latched. After the above operations, the instruction counter will be incremented.

#### #22: Transitions (Functional)
1) When state operations are complete, the controller will transition automatically to the fetch state.

### #15: FETCH (Functional)
1) Latch current address
2) Wait for data to be available to function blocks from task memories.
3) Send ctrl pulse to function blocks to begin execution.
4) Increment the current instruction number.
5) Wait for the next instruction to become available.

#### #23: Transitions (Functional)
1) To ERROR if any function block experiences an error or fault.
2) To FB_EXECUTE if the current function block indicates a state change.
3) To FETCH if a state iteration is signaled by the current function block.

### #16: FB_EXECUTE (Functional)
In this state the local sequencer will send a ctrl pulse to the function blocks to progress in state.

#### #24: Transitions (Functional)
1) To ERROR if a function block signals an error.
2) To WRITE when a function block signals a new state.

### #17: WRITE (Functional)
1) Latch the address of the current output
2) Pulse the control signal to cause a state change in the current function block.
3) Write the result of the function block to the current address.
4) Increment the instruction pointer.
5) Wait for the next instruction to be available.

#### #25: Transitions (Functional)
1) To ERROR if the current function block signals an error.
2) To FB_DONE is the current function block signals a new state.
3) To WRITE if the current function block signals a state iteration.

### #18: FB_DONE (Functional)
In this state the local sequencer will progress the state of the current function block with a ctrl pulse.

#### #26: Transitions (Functional)
1) To TASK_DONE when the function block signals a new state and the end of file flag is the current instruction.
2) To FB_SELECT otherwise when the function block signals a new state.

### #19: TASK_DONE (Functional)
The local sequencer will wait in the TASK_DONE state and signal to the global sequencer that the task is done.

#### #27: Transitions (Functional)
1) To INIT when the trigger from the global sequencer goes low.

### #20: ERROR (Functional)
The local sequencer will set pulse control if the error is recoverable in this state. If the error is not recoverable, ctrl and abort will both be pulsed simultaneously and the local sequencer will signal a task error to the global sequencer.

#### #28: Transitions (Functional)
1) To FB_SELECT if the error is recoverable.
2) To INIT if the error is not recoverable and the trigger from the global sequencer is low.

## #29: Error Signal Service Provided (Functional)
The local sequencer shall signal to the global sequencer when an unrecoverable error is encountered in a task.

## #30: Task Done Service Provided (Functional)
The local sequencer shall signal to the global sequencer when the task is complete.

## #31: Task Memory Control Service Provided (Functional)
The local sequencer shall control the address and write enable inputs to the task memories.

## #32: Instruction Pointer Service Provided (Functional)
The local sequencer shall provide a pointer to the current instruction.

## #33: Function Block Selection Service Provided (Functional)
The local sequencer shall provide a signal that indicates which function is active.

## #34: Conversion of Data Input (Functional)
Inputs to the current address and function number register shall be converted to be compatible with the respective registers.
