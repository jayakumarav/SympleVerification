# FBController_req

## #6: FBController (Functional)
The FB Controller shall provide the USER the ability to execute FB+FBD

## #7: FBController Services (Functional)
The FB controller shall provide services to FBs to permit correct + deterministic execution of FBs

### #17: FB Controller Synchronous Execution (Functional)
The FB Controller shalll assist in the Fault detection, reporting, and diagnosis of FB execution

### #18: FB Controller Set/Reset (Functional)
The FB Controller shall have the ability to set/reset state of FBs and FBDs

### #19: FB Controller Fault Detection (Functional)
The FB Controller shall assist in the Fault detection, reporting, and diagnosis of FB execution

## #8: FB Controller Watchdog (Functional)
Shall provide the ability to Reset untimely executions, mitigation actions in a task FBD

## #9: FB StateFlow Controller (Functional)
The FB state flow controller shall be a Moore state machine which Receives signals indicating the current state of the function block, and manages the state transitions in order to 1) control the function block’s correct execution and 2) catch and report any errors that arise during execution.

## #10: Input Counter (Functional)
The input counter shall record the number of input values read, indicating an error if the expected number is exceeded.

## #22: Output Counter (Functional)
The output counter shall record the number of input values written, indicating an error if the expected number is exceeded.

## #23: Counter Selector (Functional)
The counter selector shall select the input or output counter when the input STATE is in the READ or WRITE state and outputting 0 else.

## #24: Error Code Generation (Functional)
The error code generator shall generate an error code and a binary error indicator from the individual error codes passed to the function.
