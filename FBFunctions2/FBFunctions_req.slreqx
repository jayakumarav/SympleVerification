# FBFunctions_req

## #1: FB Services (Functional)
The FB shall provide services to the FB Controller to facilitiate execution of the respective function block logic.

### #3: FB Read/Write Information (Functional)
The function block shall provide the number of expected input and output values to be read and written respectively for proper execution.

### #5: FB Duplex Redundancy (Functional)
Each execution logic shall be a duplex system.

#### #7: Duplex State Comparison (Functional)
Each state comparator shall indicate an error if the FB duplex execution systems do not provide identical output.

#### #17: Duplex Execution Completion (Functional)
Each Duplex Logic block shall assert the execComplete signal once both internal simplex logic blocks have asserted the execComplete signal

### #6: Logic Execution Results (Functional)
The FB shall execute the respective logic if no errors are read prior to the execution of that logic.

#### #22: NOR Logic (Functional)
The NOR logical implementation shall take two bool or safebool values and provide the logical bool or safebool (respective) NOR operation

#### #23: AND Logic (Functional)
The AND logical implementation shall take two bool or safebool values and provide the logical bool or safebool (respective) AND operation

#### #24: NOT Logic (Functional)
The NOT logical implementation shall take one bool or safebool value and provide the logical bool or safebool (respective) NOT operation

#### #26: OR Logic (Functional)
The OR logical implementation shall take two bool or safebool values and provide the logical bool or safebool (respective) OR operation

#### #27: XOR Logic (Functional)
The XOR logical implementation shall take two bool or safebool values and provide the logical bool or safebool (respective) XOR operation

#### #28: NAND Logic (Functional)
The NAND logical implementation shall take two bool or safebool values and provide the logical bool or safebool (respective) NAND operation

#### #29: BNOR Logic (Functional)
The BNOR logical implementation shall take two bool, safebool, or integer values and provide the logical bool, safebool, or integer (respective) Bitwise NOR operation

#### #30: BAND Logic (Functional)
The BAND logical implementation shall take two bool, safebool, or integer values and provide the logical bool, safebool, or integer (respective) Bitwise AND operation

#### #31: BNOT Logic (Functional)
The BNOT logical implementation shall take one bool, safebool, or integer value and provide the logical bool, safebool, or integer (respective) Bitwise NOT operation

#### #32: BOR Logic (Functional)
The BOR logical implementation shall take two bool, safebool, or integer values and provide the logical bool, safebool, or integer (respective) Bitwise OR operation

#### #33: BXOR Logic (Functional)
The BXOR logical implementation shall take two bool, safebool, or integer values and provide the logical bool, safebool, or integer (respective) Bitwise XOR operation

#### #34: BNAND Logic (Functional)
The BNAND logical implementation shall take two bool, safebool, or integer values and provide the logical bool, safebool, or integer (respective) Bitwise NAND operation

#### #35: BSL Logic (Functional)
The BSL logical implementation shall take one integer value and provide the resultant integer Bitwise left shift operation for a single shift

#### #36: BSR Logic (Functional)
The BSR logical implementation shall take one integer value and provide the resultant integer Bitwise right shift operation for a single shift

#### #37: GT Logic (Functional)
The GT logical implementation shall take two integer or Qmn values and output a true signal if the first is "greater than" the second

#### #38: GE Logic (Functional)
The GE logical implementation shall take two integer or Qmn values and output a true signal if the first is "greater than or equal to" the second

#### #39: EQ Logic (Functional)
The EQ logical implementation shall take two integer or Qmn values and output a true signal if the first is "equal to" the second

#### #40: LT Logic (Functional)
The LT logical implementation shall take two integer or Qmn values and output a true signal if the first is "less than" the second

#### #41: LE Logic (Functional)
The LE logical implementation shall take two integer or Qmn values and output a true signal if the first is "less than or equal to" the second

#### #42: NE Logic (Functional)
The NE logical implementation shall take two integer or Qmn values and output a true signal if the first is "not equal to" the second

#### #43: MAX Logic (Functional)
The MAX logical implementation shall take two integer or Qmn values and output the greater of the two values

#### #44: MIN Logic (Functional)
The MIN logical implementation shall take two integer or Qmn values and output the lesser

#### #45: MUX Logic (Functional)
The MUX logical implementation shall take one boolean and two integer or Qmn values (do not need to match). The first integer is the MUX indicator, and the second and third values are operands. If the indicator has a value of '0', the first operand shall be written as output. If the indicator has a value of '1', the second operand shall be written as output.

#### #46: ADD Logic (Functional)
The ADD logical implementation shall take two integer or Qmn values and output a resultant integer or Qmn (respective) value equal to the "sum" of the two input values.

#### #47: SUB Logic (Functional)
The SUB logical implementation shall take two integer or Qmn values and output a resultant integer or Qmn (respective) value equal to the "difference" between the first and the second value as "output = first - second".

#### #48: MUL Logic (Functional)
The MUL logical implementation shall take two integer or Qmn values and output a resultant integer or Qmn (respective) value equal to the "product" of the two input values.

#### #49: DIV Logic (Functional)
The DIV logical implementation shall take two integer or Qmn values and output a resultant integer or Qmn (respective) value equal to the "division" between the first and the second value as "output = first / second".

#### #50: MOV Logic (Functional)

#### #58: INTtoQMN Logic (Functional)
The INTtoQMN logical implementation shall take one int value and output a Qmn value equal to the exact value of int.

#### #59: QMNtoINT Logic (Functional)
The QMNtoINT logical implementation shall take one Qmn value and output an int value equal to the rounded integer value of the Qmn. Values <0.5 ar rounded down and >=0.5 are rounded up to the nearest integer

#### #60: BOOLtoSAFEBOOL (Functional)
The BOOLtoSAFEBOOL logical implementation shall take one bool value and output a safebool value equal to the true/false value of the bool.

#### #61: SAFEBOOLtoBOOL (Functional)
The SAFEBOOLtoBOOL logical implementation shall take one safebool value and output a bool value equal to the true/false value of the safebool.

### #10: Logic Selection (Functional)
The FBFunctions shall select the proper FB logic block as indicated by the fb_select signal.

### #15: FB Output (Functional)
The FB shall output only the logic selected by the fb_select signal.

### #18: Data Reading (Functional)
The Logic block shall be enabled to read the input data into the shift register upon assertion of the enableIn signal.

#### #19: Data Read Execution (Functional)
The shift register of each logic block shall save a single value from the dataIn signal upon each low->high transition of the enable signal.

### #51: Data Writing (Functional)
The logic block shall be enabled to write the output data to the output register upon assertion of the enableResult signal and under the condition of no detected of the errors: data type error, overflow error, underflow error, divide_by_zero error

#### #52: Data Write Execution (Functional)
The output shift register of each logic block shall write a single value fro m the dataIn signal upon each low->high transition of the enable signal.

## #4: FB Errors (Functional)
The FB shall indicate if any errors occur during the execution of the FB logic.

### #12: Logical Errors (Functional)
The FB shall report any of the specified logical errors the occur during the execution of FB logic.

#### #55: Overflow (Functional)
Each logical implementation shall report an error if overflow is detected

#### #56: Underflow (Functional)
Each logical implementation shall report an error if underflow is detected

#### #57: Divide By Zero (Functional)
Each logical implementation shall report an error if division by zero is attempted

### #16: Duplex Errors (Functional)
The FB shall report all errors from both duplex blocks

### #21: Input Data Validation (Functional)
The logic block shall output an error if input data values are not as expected

#### #53: Data Type Mismatch (Functional)
Each respective logic block shall output an error if input data types do not match

#### #54: Invalid Data Type (Functional)
Each logic block shall output an error if an invalid data type is read
